"""GUI smoke test for the installed Skadis Hook workbench.

This macro is intended for a disposable FreeCAD instance. It writes a short
result log to SKADIS_GUI_SMOKE_LOG and asks the GUI to quit.
"""

import os
from pathlib import Path
import sys

import FreeCAD as App
import FreeCADGui as Gui
from FreeCAD import Vector
from PySide import QtWidgets
import Part


log_path = Path(os.environ["SKADIS_GUI_SMOKE_LOG"])
image_path = os.environ.get("SKADIS_GUI_SMOKE_IMAGE")
lines = []
document = None

try:
    workbenches = Gui.listWorkbenches()
    lines.append(f"user_appdata={App.getUserAppDataDir()}")
    lines.append(f"workbenches={','.join(sorted(workbenches))}")
    lines.append("plugin_sys_path=" + str(r"skadis-hook" in "\n".join(sys.path)).lower())
    lines.append(f"workbench_loaded={str('SkadisHookWorkbench' in workbenches).lower()}")
    Gui.activateWorkbench("SkadisHookWorkbench")

    document = App.newDocument("SkadisHookGuiSmoke")
    box = document.addObject("Part::Feature", "ProbeBox")
    box.Shape = Part.makeBox(120, 20, 80, Vector(0, 0, 0))
    document.recompute()

    Gui.Selection.clearSelection()
    Gui.Selection.addSelection(document.Name, box.Name, "Face3")
    lines.append(f"selection_count={len(Gui.Selection.getSelectionEx())}")
    Gui.runCommand("SkadisHook_Create", 0)

    hooks = [obj for obj in document.Objects if obj.Label == "Skadis 挂钩"]
    lines.append(f"hook_created={str(bool(hooks)).lower()}")
    if hooks:
        lines.append(f"hook_valid={str(hooks[0].Shape.isValid()).lower()}")
    lines.append(f"undo_mode={document.UndoMode}")
    document.undo()
    lines.append(
        "undo_removed="
        + str(not any(obj.Label == "Skadis 挂钩" for obj in document.Objects)).lower()
    )
    document.redo()
    lines.append(
        "redo_restored="
        + str(any(obj.Label == "Skadis 挂钩" for obj in document.Objects)).lower()
    )
    if image_path:
        view = Gui.activeDocument().activeView()
        view.viewAxonometric()
        Gui.SendMsgToActiveView("ViewFit")
        view.saveImage(image_path, 1000, 760, "White")
        lines.append("image_saved=" + str(Path(image_path).is_file()).lower())
    lines.append("GUI_SMOKE_OK")
except Exception as exc:
    lines.append(f"GUI_SMOKE_FAILED={type(exc).__name__}: {exc}")
finally:
    if document is not None:
        App.closeDocument(document.Name)
    log_path.write_text("\n".join(lines) + "\n", encoding="utf-8")
    QtWidgets.QApplication.instance().quit()
